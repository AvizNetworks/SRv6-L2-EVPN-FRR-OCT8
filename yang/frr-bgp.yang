// SPDX-License-Identifier: BSD-2-Clause
module frr-bgp {
  yang-version 1.1;
  namespace "http://frrouting.org/yang/bgp";
  prefix frr-bgp;

  import frr-routing {
    prefix frr-rt;
  }

  import ietf-inet-types {
    prefix inet;
  }

  import frr-interface {
    prefix frr-interface;
  }

  import frr-bgp-types {
    prefix frr-bt;
  }

  import frr-route-types {
    prefix frr-route-types;
  }

  import frr-route-map {
    prefix frr-route-map;
  }

  include "frr-bgp-common";

  include "frr-bgp-common-structure";

  include "frr-bgp-common-multiprotocol";

  include "frr-bgp-neighbor";

  include "frr-bgp-peer-group";

  include "frr-bgp-bmp";

  include "frr-bgp-evpn";

  organization
    "FRRouting";
  contact
    "FRR Users List: <mailto:frog@lists.frrouting.org> FRR Development
     List: <mailto:dev@lists.frrouting.org>";
  description
    "This module defines a model for managing FRR bgpd daemon.

     Copyright 2020 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2026-07-21 {
    description
      "Sync BGP YANG with FRR CLI: daemon-wide config, EVPN, SRv6,
       link-state, UPA, flowspec, and neighbor/AF policy gaps.";
    reference
      "FRRouting";
  }

  revision 2019-12-03 {
    description
      "Initial revision.";
    reference
      "FRRouting";
  }

  identity bgp {
    base frr-rt:routing-protocol;
    description
      "BGP protocol.";
  }

  /*
   * Daemon-wide (CONFIG_NODE) BGP configuration. Not under a
   * control-plane-protocol instance.
   */
  container bgp-daemon {
    description
      "BGP daemon-wide configuration mapped from CONFIG_NODE
       (bgp no-rib, session-dscp, community alias, queue limits, ...).";
    uses bgp-daemon-config;
  }

  grouping mp-afi-unicast-common {
    description
      "Common configuration for MP AFI unicast.";

    uses global-group-use-multiple-paths;

    uses global-redistribute;

    uses admin-distance;
  }

  augment "/frr-rt:routing/frr-rt:control-plane-protocols/frr-rt:control-plane-protocol" {
    description
      "Augments BGP protocol into routing control-plane-protocol.";

    container bgp {
      when "../frr-rt:type = 'frr-bgp:bgp'" {
        description
          "BGP protocol augmentation of frr-routing module
           control-plane-protocol.";
      }
      presence "Enables configuration of BGP";
      description
        "Top-level configuration for the BGP router.";
      container global {
        description
          "Global configuration for the BGP router.";
        leaf local-as {
          type inet:as-number;
          mandatory true;
          description
            "Local autonomous system number of the router.  Uses
             the 32-bit as-number type from the model in RFC 6991.";
        }

        uses frr-rt:router-id;

        container confederation {
          description
            "Configuration options specifying parameters when the
             local router is within an autonomous system which is
             part of a BGP confederation.";
          leaf identifier {
            type inet:as-number;
            description
              "Confederation identifier for the autonomous system.";
          }

          leaf-list member-as {
            type inet:as-number;
            description
              "Remote autonomous systems that are to be treated
               as part of the local confederation.";
          }
        }

        uses med-config;

        uses route-reflector-config;

        uses route-selection-options;

        uses global-neighbor-config;

        container graceful-restart {
          description
            "Parameters relating the graceful restart mechanism for
             BGP.";
          uses graceful-restart-config;
        }

        uses global-update-group-config;

        uses global-config-timers;

        uses global-bgp-config;

        uses global-network-config;

        uses global-graceful-shutdown;

        uses global-bmp-config;

        container segment-routing {
          description
            "BGP segment-routing configuration.
             Maps to: segment-routing srv6 under router bgp.";

          container srv6 {
            description
              "BGP SRv6 configuration.";

            leaf locator {
              type string;
              description
                "Name of the SRv6 locator configured in zebra.
                 Maps to: locator NAME.";
            }

            leaf encap-behavior {
              type enumeration {
                enum h-encaps {
                  description
                    "Use H.Encaps.";
                }
                enum h-encaps-red {
                  description
                    "Use H.Encaps.Red.";
                }
              }
              default "h-encaps";
              description
                "Headend encapsulation behavior for received SRv6 routes.
                 Maps to: encap-behavior ...";
            }

            leaf srv6-only {
              type boolean;
              default "true";
              description
                "Accept only SRv6 service routes when an SRv6 locator is
                 configured. A false value corresponds to CLI
                 'no srv6-only'.";
            }
          }
        }

        container sid-vpn-per-vrf-export {
          description
            "Per-VRF SRv6 SID for VRF-to-VPN export (both AFI).
             Maps to: sid vpn per-vrf export ... under router bgp.";

          choice sid-allocation {
            description
              "SRv6 SID allocation mode for per-VRF VPN export.";

            case index {
              leaf sid-index {
                type uint32 {
                  range "1..max";
                }
                description
                  "SRv6 SID allocation index.
                   Maps to: sid vpn per-vrf export (1-4294967295).";
              }
            }
            case automatic {
              leaf sid-auto {
                type empty;
                description
                  "Request automatic SRv6 SID allocation.
                   Maps to: sid vpn per-vrf export auto.";
              }
            }
            case explicit {
              leaf sid-explicit {
                type inet:ipv6-address;
                description
                  "Request this explicit SRv6 SID.
                   Maps to: sid vpn per-vrf export explicit X:X::X:X.";
              }
            }
          }
        }

        container afi-safis {
          description
            "List of address-families associated with the BGP
             instance.";
          list afi-safi {
            key "afi-safi-name";
            description
              "AFI, SAFI configuration available for the
               neighbour or group.";
            uses mp-afi-safi-config;

            uses mp-all-afi-safi-list-contents;
          }
        }
      }

      container neighbors {
        description
          "Configuration for BGP neighbors.";
        list neighbor {
          key "remote-address";
          description
            "List of BGP neighbors configured on the local system,
             uniquely identified by remote IPv[46] address.";
          leaf remote-address {
            type inet:ip-address;
            description
              "The remote IP address of this entry's BGP peer.";
          }

          leaf local-interface {
            type frr-interface:interface-ref {
              require-instance false;
            }
            description
              "Local interface used by this numbered peer.
               Maps to: neighbor <A.B.C.D|X:X::X:X> interface WORD.";
          }

          leaf local-port {
            type inet:port-number {
              range "0..65535";
            }
            description
              "Neighbor's BGP TCP port number.";
          }

          leaf peer-group {
            type leafref {
              path "../../../peer-groups/peer-group/peer-group-name";
            }
            description
              "The peer-group with which this neighbor is associated.";
          }

          container neighbor-remote-as {
            description
              "Remote AS configuration for BGP neighbor.";

            leaf remote-as-type {
              type frr-bt:as-type;
              mandatory true;
              description
                "Remote AS type.";
            }

            leaf remote-as {
              when "../remote-as-type = 'as-specified'";
              type inet:as-number;
              description
                "The remote autonomous system number received in
                 the BGP OPEN message.";
              reference
                "RFC 4271";
            }
          }

          uses neighbor-parameters;

          uses structure-neighbor-group-capability-options;
        }

        list unnumbered-neighbor {
          key "interface";
          description
            "List of BGP neighbors configured on the local system,
             uniquely identified by interfaces.";
          leaf interface {
            type frr-interface:interface-ref {
              require-instance false;
            }
            description
              "The local interface of this entry's BGP peer.";
          }

          leaf v6only {
            type boolean;
            default "false";
            description
              "When set to 'true' it will create a neighbor with v6
               link local only.";
          }

          leaf peer-group {
            type leafref {
              path "../../../peer-groups/peer-group/peer-group-name";
            }
            description
              "The peer-group with which this neighbor is associated.";
          }

          uses neighbor-remote-as;

          uses neighbor-parameters;

          uses structure-neighbor-group-capability-options {
            refine "frr-bgp:capability-options/extended-nexthop-capability" {
              default "true";
            }
          }
        }
      }

      container peer-groups {
        description
          "Configuration for BGP peer-groups.";
        uses bgp-peer-group-list;
      }
    }
  }

  augment "/frr-rt:routing/frr-rt:control-plane-protocols/frr-rt:control-plane-protocol/bgp/global/afi-safis/afi-safi/ipv4-unicast" {
    description
      "Augmentation for global IPv4 unicast AFI-SAFI configuration.";

    list network-config {
      key "prefix";
      description
        "A list of network routes.";
      leaf prefix {
        type inet:ipv4-prefix;
        description
          "IPv4 destination prefix.";
      }

      leaf backdoor {
        type boolean;
        default "false";
        description
          "Specify a BGP backdoor route.";
      }

      uses mp-afi-safi-network-config;
    }

    list aggregate-route {
      key "prefix";
      description
        "A list of aggregated routes.";
      leaf prefix {
        type inet:ipv4-prefix;
        description
          "IPv4 destination prefix.";
      }

      uses mp-afi-safi-agg-route-config;
    }

    list admin-distance-route {
      key "prefix";
      description
        "A list of routes with a particular admin distance.";
      leaf prefix {
        type inet:ipv4-prefix;
        description
          "IPv4 destination prefix.";
      }

      uses distance-per-route-config;
    }

    uses route-flap-dampening;

    uses mp-afi-unicast-common;

    uses global-filter-config;

    uses global-afi-safi-vpn-config;
    container upa {
      description
        "Unreachable Prefix Announcement configuration.
         Maps to: upa ... under address-family ipv4/ipv6 unicast.";

      leaf originate-all {
        type boolean;
        default "false";
        description
          "Originate UPA routes for all unreachable prefixes.
           Maps to: upa originate-all.";
      }

      leaf max-routes {
        type uint32;
        default "0";
        description
          "Maximum simultaneous globally originated UPA routes. Zero
           means unlimited. Maps to: upa max-routes.";
      }

      leaf drop {
        type boolean;
        default "false";
        description
          "Set the UPA D-bit, requesting receiver blackhole installation.
           Maps to: upa drop.";
      }
    }

    container sid-export {
      description
        "SRv6 SID export configuration for this unicast AFI.
         Maps to: sid export ... under address-family.";

      choice sid-allocation {
        description
          "SRv6 SID allocation mode.";

        case index {
          leaf sid-index {
            type uint32 {
              range "1..1048575";
            }
            description
              "SRv6 SID allocation index.";
          }
        }
        case automatic {
          leaf sid-auto {
            type empty;
            description
              "Request automatic SRv6 SID allocation.";
          }
        }
        case explicit {
          leaf sid-explicit {
            type inet:ipv6-address;
            description
              "Request this explicit SRv6 SID.";
          }
        }
      }

      leaf behavior-dt46 {
        type boolean;
        default "false";
        description
          "Use End.DT46/uDT46 instead of the AFI default behavior.";
      }

      leaf route-map {
        type frr-route-map:route-map-ref;
        description
          "Route map selecting routes for SID export.";
      }
    }
  }

  augment "/frr-rt:routing/frr-rt:control-plane-protocols/frr-rt:control-plane-protocol/bgp/global/afi-safis/afi-safi/ipv6-unicast" {
    description
      "Augmentation for global IPv6 unicast AFI-SAFI configuration.";

    list network-config {
      key "prefix";
      description
        "A list of network routes.";
      leaf prefix {
        type inet:ipv6-prefix;
        description
          "IPv6 destination prefix.";
      }

      leaf backdoor {
        type boolean;
        default "false";
        description
          "Specify a BGP backdoor route.";
      }

      uses mp-afi-safi-network-config;
    }

    list aggregate-route {
      key "prefix";
      description
        "A list of aggregated routes.";
      leaf prefix {
        type inet:ipv6-prefix;
        description
          "IPv6 destination prefix.";
      }

      uses mp-afi-safi-agg-route-config;
    }

    list admin-distance-route {
      key "prefix";
      description
        "A list of routes with a particular admin distance.";
      leaf prefix {
        type inet:ipv6-prefix;
        description
          "IPv6 destination prefix.";
      }

      uses distance-per-route-config;
    }

    uses route-flap-dampening;

    uses mp-afi-unicast-common;

    uses ipv6-nexthop-prefer-global;

    uses global-filter-config;

    uses global-afi-safi-vpn-config;
    container upa {
      description
        "Unreachable Prefix Announcement configuration.
         Maps to: upa ... under address-family ipv4/ipv6 unicast.";

      leaf originate-all {
        type boolean;
        default "false";
        description
          "Originate UPA routes for all unreachable prefixes.
           Maps to: upa originate-all.";
      }

      leaf max-routes {
        type uint32;
        default "0";
        description
          "Maximum simultaneous globally originated UPA routes. Zero
           means unlimited. Maps to: upa max-routes.";
      }

      leaf drop {
        type boolean;
        default "false";
        description
          "Set the UPA D-bit, requesting receiver blackhole installation.
           Maps to: upa drop.";
      }
    }

    container sid-export {
      description
        "SRv6 SID export configuration for this unicast AFI.
         Maps to: sid export ... under address-family.";

      choice sid-allocation {
        description
          "SRv6 SID allocation mode.";

        case index {
          leaf sid-index {
            type uint32 {
              range "1..1048575";
            }
            description
              "SRv6 SID allocation index.";
          }
        }
        case automatic {
          leaf sid-auto {
            type empty;
            description
              "Request automatic SRv6 SID allocation.";
          }
        }
        case explicit {
          leaf sid-explicit {
            type inet:ipv6-address;
            description
              "Request this explicit SRv6 SID.";
          }
        }
      }

      leaf behavior-dt46 {
        type boolean;
        default "false";
        description
          "Use End.DT46/uDT46 instead of the AFI default behavior.";
      }

      leaf route-map {
        type frr-route-map:route-map-ref;
        description
          "Route map selecting routes for SID export.";
      }
    }
  }

  augment "/frr-rt:routing/frr-rt:control-plane-protocols/frr-rt:control-plane-protocol/bgp/global/afi-safis/afi-safi/ipv4-labeled-unicast" {
    description
      "Augmentation for global IPv4 labeled unicast AFI-SAFI configuration.";

    list network-config {
      key "prefix";
      description
        "A list of network routes.";
      leaf prefix {
        type inet:ipv4-prefix;
        description
          "IPv4 destination prefix.";
      }

      leaf backdoor {
        type boolean;
        default "false";
        description
          "Specify a BGP backdoor route.";
      }

      uses mp-afi-safi-network-config;
    }

    list aggregate-route {
      key "prefix";
      description
        "A list of aggregated routes.";
      leaf prefix {
        type inet:ipv4-prefix;
        description
          "IPv4 destination prefix.";
      }

      uses mp-afi-safi-agg-route-config;
    }

    uses global-group-use-multiple-paths;

    uses route-flap-dampening;
  }

  augment "/frr-rt:routing/frr-rt:control-plane-protocols/frr-rt:control-plane-protocol/bgp/global/afi-safis/afi-safi/ipv6-labeled-unicast" {
    description
      "Augmentation for global IPv6 labeled unicast AFI-SAFI configuration.";

    list network-config {
      key "prefix";
      description
        "A list of network routes.";
      leaf prefix {
        type inet:ipv6-prefix;
        description
          "IPv6 destination prefix.";
      }

      leaf backdoor {
        type boolean;
        default "false";
        description
          "Specify a BGP backdoor route.";
      }

      uses mp-afi-safi-network-config;
    }

    list aggregate-route {
      key "prefix";
      description
        "A list of aggregated routes.";
      leaf prefix {
        type inet:ipv6-prefix;
        description
          "IPv6 destination prefix.";
      }

      uses mp-afi-safi-agg-route-config;
    }

    uses global-group-use-multiple-paths;

    uses route-flap-dampening;

    uses ipv6-nexthop-prefer-global;
  }

  augment "/frr-rt:routing/frr-rt:control-plane-protocols/frr-rt:control-plane-protocol/bgp/global/afi-safis/afi-safi/ipv4-multicast" {
    description
      "Augmentation for global IPv4 multicast AFI-SAFI configuration.";

    list network-config {
      key "prefix";
      description
        "A list of network routes.";
      leaf prefix {
        type frr-route-types:ipv4-multicast-group-prefix;
        description
          "IPv4 multicast destination prefix.";
      }

      leaf backdoor {
        type boolean;
        default "false";
        description
          "Specify a BGP backdoor route.";
      }

      uses mp-afi-safi-network-config;
    }

    list aggregate-route {
      key "prefix";
      description
        "A list of aggregated routes.";
      leaf prefix {
        type frr-route-types:ipv4-multicast-group-prefix;
        description
          "IPv4 multicast destination prefix.";
      }

      uses mp-afi-safi-agg-route-config;
    }

    list admin-distance-route {
      key "prefix";
      description
        "A list of routes with a particular admin distance.";
      leaf prefix {
        type frr-route-types:ipv4-multicast-group-prefix;
        description
          "IPv4 multicast destination prefix.";
      }

      uses distance-per-route-config;
    }

    uses admin-distance;

    uses route-flap-dampening;

    uses global-filter-config;
  }

  augment "/frr-rt:routing/frr-rt:control-plane-protocols/frr-rt:control-plane-protocol/bgp/global/afi-safis/afi-safi/ipv6-multicast" {
    description
      "Augmentation for global IPv6 multicast AFI-SAFI configuration.";

    list network-config {
      key "prefix";
      description
        "A list of network routes.";
      leaf prefix {
        type frr-route-types:ipv6-multicast-group-prefix;
        description
          "IPv6 multicast destination prefix.";
      }

      leaf backdoor {
        type boolean;
        default "false";
        description
          "Specify a BGP backdoor route.";
      }

      uses mp-afi-safi-network-config;
    }

    list aggregate-route {
      key "prefix";
      description
        "A list of aggregated routes.";
      leaf prefix {
        type frr-route-types:ipv6-multicast-group-prefix;
        description
          "IPv6 multicast destination prefix.";
      }

      uses mp-afi-safi-agg-route-config;
    }

    list admin-distance-route {
      key "prefix";
      description
        "A list of routes with a particular admin distance.";
      leaf prefix {
        type frr-route-types:ipv6-multicast-group-prefix;
        description
          "IPv6 multicast destination prefix.";
      }

      uses distance-per-route-config;
    }

    uses route-flap-dampening;

    uses admin-distance;

    uses ipv6-nexthop-prefer-global;
  }


  augment "/frr-rt:routing/frr-rt:control-plane-protocols/frr-rt:control-plane-protocol/bgp/global/afi-safis/afi-safi/l2vpn-evpn" {
    description
      "Augmentation for global L2VPN EVPN AFI-SAFI configuration.";

    uses global-evpn-config;

    uses srv6-l2-evpn-config;
  }

  augment "/frr-rt:routing/frr-rt:control-plane-protocols/frr-rt:control-plane-protocol/bgp/global/afi-safis/afi-safi/link-state" {
    description
      "Augmentation for global BGP Link-State AFI-SAFI configuration.";

    container distribute {
      description
        "BGP Link-State topology distribution.";

      container bgp-fabric-link-state {
        presence "Enable BGP fabric link-state topology distribution.";
        description
          "Export locally learned BGP fabric topology as BGP-LS NLRIs.
           Maps to: distribute bgp-fabric-link-state.";

        leaf instance-id {
          type uint64;
          default "0";
          description
            "BGP-LS instance identifier.";
        }
      }
    }
  }

  augment "/frr-rt:routing/frr-rt:control-plane-protocols/frr-rt:control-plane-protocol/bgp/global/afi-safis/afi-safi/ipv4-flowspec" {
    description
      "Augmentation for global IPv4 flowspec AFI-SAFI configuration.";

    uses flow-spec-config;
  }

  augment "/frr-rt:routing/frr-rt:control-plane-protocols/frr-rt:control-plane-protocol/bgp/global/afi-safis/afi-safi/ipv6-flowspec" {
    description
      "Augmentation for global IPv6 flowspec AFI-SAFI configuration.";

    uses flow-spec-config;
  }

  augment "/frr-rt:routing/frr-rt:control-plane-protocols/frr-rt:control-plane-protocol/bgp/global/afi-safis/afi-safi/l3vpn-ipv4-unicast" {
    description
      "Augmentation for global L3VPN IPv4 unicast AFI-SAFI configuration.";

    uses global-afi-safi-vpn-network-config;

    uses vpn-retain-route-target-config;
  }

  augment "/frr-rt:routing/frr-rt:control-plane-protocols/frr-rt:control-plane-protocol/bgp/global/afi-safis/afi-safi/l3vpn-ipv6-unicast" {
    description
      "Augmentation for global L3VPN IPv6 unicast AFI-SAFI configuration.";

    uses global-afi-safi-vpn-network-config;

    uses vpn-retain-route-target-config;
  }

  augment "/frr-rt:routing/frr-rt:control-plane-protocols/frr-rt:control-plane-protocol/bgp/global/bmp-config/target-list/afi-safis/afi-safi/ipv4-unicast" {
    description
      "Augmentation for BMP IPv4 unicast AFI-SAFI configuration.";

    uses bmp-afi-safi-common-config;
  }

  augment "/frr-rt:routing/frr-rt:control-plane-protocols/frr-rt:control-plane-protocol/bgp/global/bmp-config/target-list/afi-safis/afi-safi/ipv4-multicast" {
    description
      "Augmentation for BMP IPv4 multicast AFI-SAFI configuration.";

    uses bmp-afi-safi-common-config;
  }

  augment "/frr-rt:routing/frr-rt:control-plane-protocols/frr-rt:control-plane-protocol/bgp/global/bmp-config/target-list/afi-safis/afi-safi/ipv6-unicast" {
    description
      "Augmentation for BMP IPv6 unicast AFI-SAFI configuration.";

    uses bmp-afi-safi-common-config;
  }

  augment "/frr-rt:routing/frr-rt:control-plane-protocols/frr-rt:control-plane-protocol/bgp/global/bmp-config/target-list/afi-safis/afi-safi/ipv6-multicast" {
    description
      "Augmentation for BMP IPv6 multicast AFI-SAFI configuration.";

    uses bmp-afi-safi-common-config;
  }

  augment "/frr-rt:routing/frr-rt:control-plane-protocols/frr-rt:control-plane-protocol/bgp/global/bmp-config/target-list/afi-safis/afi-safi/l3vpn-ipv4-unicast" {
    description
      "Augmentation for BMP L3VPN IPv4 unicast AFI-SAFI configuration.";

    uses bmp-afi-safi-common-config;
  }

  augment "/frr-rt:routing/frr-rt:control-plane-protocols/frr-rt:control-plane-protocol/bgp/global/bmp-config/target-list/afi-safis/afi-safi/l3vpn-ipv6-unicast" {
    description
      "Augmentation for BMP L3VPN IPv6 unicast AFI-SAFI configuration.";

    uses bmp-afi-safi-common-config;
  }

  augment "/frr-rt:routing/frr-rt:control-plane-protocols/frr-rt:control-plane-protocol/bgp/global/bmp-config/target-list/afi-safis/afi-safi/l2vpn-evpn" {
    description
      "Augmentation for BMP L2VPN EVPN AFI-SAFI configuration.";

    uses bmp-afi-safi-common-config;
  }

  augment "/frr-rt:routing/frr-rt:control-plane-protocols/frr-rt:control-plane-protocol/bgp/neighbors/neighbor/afi-safis/afi-safi/ipv4-unicast" {
    description
      "Augmentation for neighbor IPv4 unicast AFI-SAFI configuration.";

    uses structure-neighbor-group-add-paths;

    uses structure-neighbor-group-as-path-options;

    uses structure-neighbor-default-originate-options;

    uses structure-neighbor-prefix-limit;

    uses structure-neighbor-nexthop-self;

    uses structure-neighbor-private-as;

    uses structure-neighbor-weight;

    uses structure-neighbor-route-reflector;

    uses structure-neighbor-route-server;

    uses structure-neighbor-send-community;

    uses structure-neighbor-group-soft-reconfiguration;

    uses structure-neighbor-group-attr-unchanged;

    uses structure-neighbor-group-orf-capability;

    uses structure-neighbor-group-af-policy-options;

    uses structure-neighbor-group-encapsulation;

    uses structure-neighbor-group-filter-config;

    uses route-flap-dampening;
  }

  augment "/frr-rt:routing/frr-rt:control-plane-protocols/frr-rt:control-plane-protocol/bgp/neighbors/neighbor/afi-safis/afi-safi/ipv6-unicast" {
    description
      "Augmentation for neighbor IPv6 unicast AFI-SAFI configuration.";

    leaf nexthop-local-unchanged {
      type boolean;
      default "false";
      description
        "Configure treatment of outgoing link-local nexthop attribute.
         When set to 'true' it leaves link-local nexthop unchanged
         for this peer.";
    }

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-encapsulation;

    uses structure-neighbor-group-filter-config;

    uses route-flap-dampening;
  }

  augment "/frr-rt:routing/frr-rt:control-plane-protocols/frr-rt:control-plane-protocol/bgp/neighbors/neighbor/afi-safis/afi-safi/ipv4-multicast" {
    description
      "Augmentation for neighbor IPv4 multicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
  }

  augment "/frr-rt:routing/frr-rt:control-plane-protocols/frr-rt:control-plane-protocol/bgp/neighbors/neighbor/afi-safis/afi-safi/ipv6-multicast" {
    description
      "Augmentation for neighbor IPv6 multicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
   }

  augment "/frr-rt:routing/frr-rt:control-plane-protocols/frr-rt:control-plane-protocol/bgp/neighbors/neighbor/afi-safis/afi-safi/ipv4-labeled-unicast" {
    description
      "Augmentation for neighbor IPv4 labeled unicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
  }

  augment "/frr-rt:routing/frr-rt:control-plane-protocols/frr-rt:control-plane-protocol/bgp/neighbors/neighbor/afi-safis/afi-safi/ipv6-labeled-unicast" {
    description
      "Augmentation for neighbor IPv6 labeled unicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
  }

  augment "/frr-rt:routing/frr-rt:control-plane-protocols/frr-rt:control-plane-protocol/bgp/neighbors/neighbor/afi-safis/afi-safi/l3vpn-ipv4-unicast" {
    description
      "Augmentation for neighbor L3VPN IPv4 unicast AFI-SAFI configuration.";

    uses structure-neighbor-group-add-paths;

    uses structure-neighbor-group-as-path-options;

    uses structure-neighbor-group-attr-unchanged;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-encapsulation;

    uses structure-neighbor-group-filter-config;
  }

  augment "/frr-rt:routing/frr-rt:control-plane-protocols/frr-rt:control-plane-protocol/bgp/neighbors/neighbor/afi-safis/afi-safi/l3vpn-ipv6-unicast" {
    description
      "Augmentation for neighbor L3VPN IPv6 unicast AFI-SAFI configuration.";

    uses structure-neighbor-group-add-paths;

    uses structure-neighbor-group-as-path-options;

    uses structure-neighbor-group-attr-unchanged;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-encapsulation;

    uses structure-neighbor-group-filter-config;
  }

  augment "/frr-rt:routing/frr-rt:control-plane-protocols/frr-rt:control-plane-protocol/bgp/neighbors/neighbor/afi-safis/afi-safi/l2vpn-evpn" {
    description
      "Augmentation for neighbor L2VPN EVPN AFI-SAFI configuration.";

    uses structure-neighbor-group-add-paths;

    uses structure-neighbor-group-as-path-options;

    uses structure-neighbor-group-attr-unchanged;

    uses structure-neighbor-prefix-limit;

    uses structure-neighbor-nexthop-self;

    uses structure-neighbor-route-reflector;

    uses structure-neighbor-route-server;

    uses structure-neighbor-group-soft-reconfiguration;

    uses structure-neighbor-group-af-policy-options;

    uses structure-neighbor-group-filter-config;
  }

  augment "/frr-rt:routing/frr-rt:control-plane-protocols/frr-rt:control-plane-protocol/bgp/neighbors/neighbor/afi-safis/afi-safi/ipv4-flowspec" {
    description
      "Augmentation for neighbor IPv4 flowspec AFI-SAFI configuration.";

    uses structure-neighbor-route-reflector;

    uses structure-neighbor-route-server;

    uses structure-neighbor-group-soft-reconfiguration;

    uses structure-neighbor-group-af-policy-options;

    uses structure-neighbor-group-filter-config;
  }

  augment "/frr-rt:routing/frr-rt:control-plane-protocols/frr-rt:control-plane-protocol/bgp/neighbors/neighbor/afi-safis/afi-safi/ipv6-flowspec" {
    description
      "Augmentation for neighbor IPv6 flowspec AFI-SAFI configuration.";

    uses structure-neighbor-route-reflector;

    uses structure-neighbor-route-server;

    uses structure-neighbor-group-soft-reconfiguration;

    uses structure-neighbor-group-af-policy-options;

    uses structure-neighbor-group-filter-config;
  }

  augment "/frr-rt:routing/frr-rt:control-plane-protocols/frr-rt:control-plane-protocol/bgp/neighbors/neighbor/afi-safis/afi-safi/link-state" {
    description
      "Augmentation for neighbor Link-State AFI-SAFI configuration.";

    uses structure-neighbor-group-filter-config;
  }

  augment "/frr-rt:routing/frr-rt:control-plane-protocols/frr-rt:control-plane-protocol/bgp/neighbors/neighbor/afi-safis/afi-safi/ipv4-unreachability" {
    description
      "Augmentation for neighbor IPv4 unreachability AFI-SAFI configuration.";

    uses structure-neighbor-group-as-path-options;

    uses structure-neighbor-prefix-limit;

    uses structure-neighbor-group-filter-config;
  }

  augment "/frr-rt:routing/frr-rt:control-plane-protocols/frr-rt:control-plane-protocol/bgp/neighbors/neighbor/afi-safis/afi-safi/ipv6-unreachability" {
    description
      "Augmentation for neighbor IPv6 unreachability AFI-SAFI configuration.";

    uses structure-neighbor-group-as-path-options;

    uses structure-neighbor-prefix-limit;

    uses structure-neighbor-group-filter-config;
  }

  augment "/frr-rt:routing/frr-rt:control-plane-protocols/frr-rt:control-plane-protocol/bgp/neighbors/unnumbered-neighbor/afi-safis/afi-safi/ipv4-unicast" {
    description
      "Augmentation for unnumbered neighbor IPv4 unicast AFI-SAFI configuration.";

    uses structure-neighbor-group-add-paths;

    uses structure-neighbor-group-as-path-options;

    uses structure-neighbor-default-originate-options;

    uses structure-neighbor-prefix-limit;

    uses structure-neighbor-nexthop-self;

    uses structure-neighbor-private-as;

    uses structure-neighbor-weight;

    uses structure-neighbor-route-reflector;

    uses structure-neighbor-route-server;

    uses structure-neighbor-send-community;

    uses structure-neighbor-group-soft-reconfiguration;

    uses structure-neighbor-group-attr-unchanged;

    uses structure-neighbor-group-orf-capability;

    uses structure-neighbor-group-af-policy-options;

    uses structure-neighbor-group-encapsulation;

    uses structure-neighbor-group-filter-config;

    uses route-flap-dampening;
  }

  augment "/frr-rt:routing/frr-rt:control-plane-protocols/frr-rt:control-plane-protocol/bgp/neighbors/unnumbered-neighbor/afi-safis/afi-safi/ipv6-unicast" {
    description
      "Augmentation for unnumbered neighbor IPv6 unicast AFI-SAFI configuration.";

    leaf nexthop-local-unchanged {
      type boolean;
      default "false";
      description
        "Configure treatment of outgoing link-local nexthop attribute.
         When set to 'true' it leaves link-local nexthop unchanged
         for this peer.";
    }

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-encapsulation;

    uses structure-neighbor-group-filter-config;

    uses route-flap-dampening;
  }

  augment "/frr-rt:routing/frr-rt:control-plane-protocols/frr-rt:control-plane-protocol/bgp/neighbors/unnumbered-neighbor/afi-safis/afi-safi/ipv4-multicast" {
    description
      "Augmentation for unnumbered neighbor IPv4 multicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
  }

  augment "/frr-rt:routing/frr-rt:control-plane-protocols/frr-rt:control-plane-protocol/bgp/neighbors/unnumbered-neighbor/afi-safis/afi-safi/ipv6-multicast" {
    description
      "Augmentation for unnumbered neighbor IPv6 multicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
  }

  augment "/frr-rt:routing/frr-rt:control-plane-protocols/frr-rt:control-plane-protocol/bgp/neighbors/unnumbered-neighbor/afi-safis/afi-safi/ipv4-labeled-unicast" {
    description
      "Augmentation for unnumbered neighbor IPv4 labeled unicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
  }

  augment "/frr-rt:routing/frr-rt:control-plane-protocols/frr-rt:control-plane-protocol/bgp/neighbors/unnumbered-neighbor/afi-safis/afi-safi/ipv6-labeled-unicast" {
    description
      "Augmentation for unnumbered neighbor IPv6 labeled unicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;
    uses route-flap-dampening;

  }

  augment "/frr-rt:routing/frr-rt:control-plane-protocols/frr-rt:control-plane-protocol/bgp/neighbors/unnumbered-neighbor/afi-safis/afi-safi/l3vpn-ipv4-unicast" {
    description
      "Augmentation for unnumbered neighbor L3VPN IPv4 unicast AFI-SAFI configuration.";

    uses structure-neighbor-group-add-paths;

    uses structure-neighbor-group-as-path-options;

    uses structure-neighbor-group-attr-unchanged;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-group-encapsulation;

    uses structure-neighbor-weight;
  }

  augment "/frr-rt:routing/frr-rt:control-plane-protocols/frr-rt:control-plane-protocol/bgp/neighbors/unnumbered-neighbor/afi-safis/afi-safi/l3vpn-ipv6-unicast" {
    description
      "Augmentation for unnumbered neighbor L3VPN IPv6 unicast AFI-SAFI configuration.";

    uses structure-neighbor-group-add-paths;

    uses structure-neighbor-group-as-path-options;

    uses structure-neighbor-group-attr-unchanged;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-group-encapsulation;

    uses structure-neighbor-weight;
  }

  augment "/frr-rt:routing/frr-rt:control-plane-protocols/frr-rt:control-plane-protocol/bgp/neighbors/unnumbered-neighbor/afi-safis/afi-safi/l2vpn-evpn" {
    description
      "Augmentation for unnumbered neighbor L2VPN EVPN AFI-SAFI configuration.";

    uses structure-neighbor-group-add-paths;

    uses structure-neighbor-group-as-path-options;

    uses structure-neighbor-group-attr-unchanged;

    uses structure-neighbor-prefix-limit;

    uses structure-neighbor-nexthop-self;

    uses structure-neighbor-route-reflector;

    uses structure-neighbor-route-server;

    uses structure-neighbor-group-soft-reconfiguration;

    uses structure-neighbor-group-af-policy-options;

    uses structure-neighbor-group-filter-config;
  }

  augment "/frr-rt:routing/frr-rt:control-plane-protocols/frr-rt:control-plane-protocol/bgp/neighbors/unnumbered-neighbor/afi-safis/afi-safi/ipv4-flowspec" {
    description
      "Augmentation for unnumbered neighbor IPv4 flowspec AFI-SAFI configuration.";

    uses structure-neighbor-route-reflector;

    uses structure-neighbor-route-server;

    uses structure-neighbor-group-soft-reconfiguration;

    uses structure-neighbor-group-af-policy-options;

    uses structure-neighbor-group-filter-config;
  }

  augment "/frr-rt:routing/frr-rt:control-plane-protocols/frr-rt:control-plane-protocol/bgp/neighbors/unnumbered-neighbor/afi-safis/afi-safi/ipv6-flowspec" {
    description
      "Augmentation for unnumbered neighbor IPv6 flowspec AFI-SAFI configuration.";

    uses structure-neighbor-route-reflector;

    uses structure-neighbor-route-server;

    uses structure-neighbor-group-soft-reconfiguration;

    uses structure-neighbor-group-af-policy-options;

    uses structure-neighbor-group-filter-config;
  }

  augment "/frr-rt:routing/frr-rt:control-plane-protocols/frr-rt:control-plane-protocol/bgp/neighbors/unnumbered-neighbor/afi-safis/afi-safi/link-state" {
    description
      "Augmentation for unnumbered neighbor Link-State AFI-SAFI configuration.";

    uses structure-neighbor-group-filter-config;
  }

  augment "/frr-rt:routing/frr-rt:control-plane-protocols/frr-rt:control-plane-protocol/bgp/neighbors/unnumbered-neighbor/afi-safis/afi-safi/ipv4-unreachability" {
    description
      "Augmentation for unnumbered neighbor IPv4 unreachability AFI-SAFI configuration.";

    uses structure-neighbor-group-as-path-options;

    uses structure-neighbor-prefix-limit;

    uses structure-neighbor-group-filter-config;
  }

  augment "/frr-rt:routing/frr-rt:control-plane-protocols/frr-rt:control-plane-protocol/bgp/neighbors/unnumbered-neighbor/afi-safis/afi-safi/ipv6-unreachability" {
    description
      "Augmentation for unnumbered neighbor IPv6 unreachability AFI-SAFI configuration.";

    uses structure-neighbor-group-as-path-options;

    uses structure-neighbor-prefix-limit;

    uses structure-neighbor-group-filter-config;
  }

  augment "/frr-rt:routing/frr-rt:control-plane-protocols/frr-rt:control-plane-protocol/bgp/peer-groups/peer-group/afi-safis/afi-safi/ipv4-unicast" {
    description
      "Augmentation for peer-group IPv4 unicast AFI-SAFI configuration.";

    uses structure-neighbor-group-add-paths;

    uses structure-neighbor-group-as-path-options;

    uses structure-neighbor-default-originate-options;

    uses structure-neighbor-prefix-limit;

    uses structure-neighbor-nexthop-self;

    uses structure-neighbor-private-as;

    uses structure-neighbor-weight;

    uses structure-neighbor-route-reflector;

    uses structure-neighbor-route-server;

    uses structure-neighbor-send-community;

    uses structure-neighbor-group-soft-reconfiguration;

    uses structure-neighbor-group-attr-unchanged;

    uses structure-neighbor-group-orf-capability;

    uses structure-neighbor-group-af-policy-options;

    uses structure-neighbor-group-encapsulation;

    uses structure-neighbor-group-filter-config;

    uses route-flap-dampening;
  }

  augment "/frr-rt:routing/frr-rt:control-plane-protocols/frr-rt:control-plane-protocol/bgp/peer-groups/peer-group/afi-safis/afi-safi/ipv6-unicast" {
    description
      "Augmentation for peer-group IPv6 unicast AFI-SAFI configuration.";

    leaf nexthop-local-unchanged {
      type boolean;
      default "false";
      description
        "Configure treatment of outgoing link-local nexthop attribute.
         When set to 'true' it leaves link-local nexthop unchanged
         for this peer.";
    }

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-encapsulation;

    uses structure-neighbor-group-filter-config;

    uses route-flap-dampening;
  }

  augment "/frr-rt:routing/frr-rt:control-plane-protocols/frr-rt:control-plane-protocol/bgp/peer-groups/peer-group/afi-safis/afi-safi/ipv4-multicast" {
    description
      "Augmentation for peer-group IPv4 multicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
  }

  augment "/frr-rt:routing/frr-rt:control-plane-protocols/frr-rt:control-plane-protocol/bgp/peer-groups/peer-group/afi-safis/afi-safi/ipv6-multicast" {
    description
      "Augmentation for peer-group IPv6 multicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
  }

  augment "/frr-rt:routing/frr-rt:control-plane-protocols/frr-rt:control-plane-protocol/bgp/peer-groups/peer-group/afi-safis/afi-safi/ipv4-labeled-unicast" {
    description
      "Augmentation for peer-group IPv4 labeled unicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
  }

  augment "/frr-rt:routing/frr-rt:control-plane-protocols/frr-rt:control-plane-protocol/bgp/peer-groups/peer-group/afi-safis/afi-safi/ipv6-labeled-unicast" {
    description
      "Augmentation for peer-group IPv6 labeled unicast AFI-SAFI configuration.";

    uses structure-neighbor-group-add-paths;

    uses structure-neighbor-group-as-path-options;

    uses structure-neighbor-default-originate-options;

    uses structure-neighbor-group-attr-unchanged;

    uses structure-neighbor-group-orf-capability;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-filter-config;

    uses route-flap-dampening;
  }

  augment "/frr-rt:routing/frr-rt:control-plane-protocols/frr-rt:control-plane-protocol/bgp/peer-groups/peer-group/afi-safis/afi-safi/l3vpn-ipv4-unicast" {
    description
      "Augmentation for peer-group L3VPN IPv4 unicast AFI-SAFI configuration.";

    uses structure-neighbor-group-add-paths;

    uses structure-neighbor-group-as-path-options;

    uses structure-neighbor-group-attr-unchanged;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-encapsulation;

    uses structure-neighbor-group-filter-config;
  }

  augment "/frr-rt:routing/frr-rt:control-plane-protocols/frr-rt:control-plane-protocol/bgp/peer-groups/peer-group/afi-safis/afi-safi/l3vpn-ipv6-unicast" {
    description
      "Augmentation for peer-group L3VPN IPv6 unicast AFI-SAFI configuration.";

    uses structure-neighbor-group-add-paths;

    uses structure-neighbor-group-as-path-options;

    uses structure-neighbor-group-attr-unchanged;

    uses structure-neighbor-prefix-limit;

    uses structure-neighbor-nexthop-self;

    uses structure-neighbor-private-as;

    uses structure-neighbor-route-reflector;

    uses structure-neighbor-route-server;

    uses structure-neighbor-send-community;

    uses structure-neighbor-group-soft-reconfiguration;

    uses structure-neighbor-weight;

    uses structure-neighbor-group-af-policy-options;

    uses structure-neighbor-group-encapsulation;

    uses structure-neighbor-group-filter-config;
  }

  augment "/frr-rt:routing/frr-rt:control-plane-protocols/frr-rt:control-plane-protocol/bgp/peer-groups/peer-group/afi-safis/afi-safi/l2vpn-evpn" {
    description
      "Augmentation for peer-group L2VPN EVPN AFI-SAFI configuration.";

    uses structure-neighbor-group-add-paths;

    uses structure-neighbor-group-as-path-options;

    uses structure-neighbor-group-attr-unchanged;

    uses structure-neighbor-prefix-limit;

    uses structure-neighbor-nexthop-self;

    uses structure-neighbor-route-reflector;

    uses structure-neighbor-route-server;

    uses structure-neighbor-group-soft-reconfiguration;

    uses structure-neighbor-group-af-policy-options;

    uses structure-neighbor-group-filter-config;
  }

  augment "/frr-rt:routing/frr-rt:control-plane-protocols/frr-rt:control-plane-protocol/bgp/peer-groups/peer-group/afi-safis/afi-safi/ipv4-flowspec" {
    description
      "Augmentation for peer-group IPv4 flowspec AFI-SAFI configuration.";

    uses structure-neighbor-route-reflector;

    uses structure-neighbor-route-server;

    uses structure-neighbor-group-soft-reconfiguration;

    uses structure-neighbor-group-af-policy-options;

    uses structure-neighbor-group-filter-config;
  }

  augment "/frr-rt:routing/frr-rt:control-plane-protocols/frr-rt:control-plane-protocol/bgp/peer-groups/peer-group/afi-safis/afi-safi/ipv6-flowspec" {
    description
      "Augmentation for peer-group IPv6 flowspec AFI-SAFI configuration.";

    uses structure-neighbor-route-reflector;

    uses structure-neighbor-route-server;

    uses structure-neighbor-group-soft-reconfiguration;

    uses structure-neighbor-group-af-policy-options;

    uses structure-neighbor-group-filter-config;
  }

  augment "/frr-rt:routing/frr-rt:control-plane-protocols/frr-rt:control-plane-protocol/bgp/peer-groups/peer-group/afi-safis/afi-safi/link-state" {
    description
      "Augmentation for peer-group Link-State AFI-SAFI configuration.";

    uses structure-neighbor-group-filter-config;
  }

  augment "/frr-rt:routing/frr-rt:control-plane-protocols/frr-rt:control-plane-protocol/bgp/peer-groups/peer-group/afi-safis/afi-safi/ipv4-unreachability" {
    description
      "Augmentation for peer-group IPv4 unreachability AFI-SAFI configuration.";

    uses structure-neighbor-group-as-path-options;

    uses structure-neighbor-prefix-limit;

    uses structure-neighbor-group-filter-config;
  }

  augment "/frr-rt:routing/frr-rt:control-plane-protocols/frr-rt:control-plane-protocol/bgp/peer-groups/peer-group/afi-safis/afi-safi/ipv6-unreachability" {
    description
      "Augmentation for peer-group IPv6 unreachability AFI-SAFI configuration.";

    uses structure-neighbor-group-as-path-options;

    uses structure-neighbor-prefix-limit;

    uses structure-neighbor-group-filter-config;
  }

  augment "/frr-interface:lib/frr-interface:interface" {
    description
      "Augments interface model with BGP MPLS forwarding knobs.";

    leaf mpls-bgp-forwarding {
      type boolean;
      default "false";
      description
        "Enable MPLS forwarding for eBGP directly connected peers.";
    }

    leaf mpls-l3vpn-multi-domain-switching {
      type boolean;
      default "false";
      description
        "Bind a local MPLS label to incoming L3VPN updates on this
         interface.";
    }
  }
}
